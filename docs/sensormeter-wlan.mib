-- ===========================================================================
-- SENSORMETER-WLAN-MIB
--
-- Tool-unabhaengige SNMPv2-SMI-MIB fuer das Sensormeter-WLAN-Projekt
-- (generisches ESP32-WROOM-32-DevKit, WLAN-only, 1x DHT22).
--
-- WICHTIGER HINWEIS ZUR ENTERPRISE-OID:
-- Die hier verwendete Enterprise-Nummer 99999 unter .1.3.6.1.4.1 ist eine
-- inoffizielle, NICHT bei der IANA registrierte Platzhalter-OID fuer dieses
-- Hobby-Projekt. Sie ist NICHT bei der IANA (Internet Assigned Numbers
-- Authority) eingetragen und darf nicht mit einer echten, offiziell
-- zugeteilten Enterprise-Number verwechselt werden. Gedacht ausschliesslich
-- fuer den privaten Einsatz in einem geschlossenen Netz - NICHT fuer
-- oeffentliche oder kommerzielle Nutzung ohne eine eigene, bei der IANA
-- registrierte Enterprise-Number (Registrierung unter
-- https://www.iana.org/assignments/enterprise-numbers). Wer diese MIB
-- weiterverwendet, muss sich dessen bewusst sein.
--
-- Ground truth fuer alle OIDs: firmware/src/SNMPManager.cpp/.h in diesem
-- Repository (nicht das Zabbix-YAML-Template, das nur als Kreuzreferenz
-- diente). Basis-OID-Struktur identisch zu Sensormeter (WT32-ETH01) und
-- Sensormeter PoE (WLAN-IP auf .2.2.0, RSSI auf .2.3.0), ABER dieses
-- Projekt hat kein LAN-Interface und keinen zweiten Sensor: .2.1.0
-- (LAN-IP) und der komplette .4.x-Sensor-2-Zweig bleiben unbeantwortet
-- und sind deshalb bewusst NICHT als OBJECT-TYPE in dieser MIB
-- deklariert (ein Tool, das dort pollt, wuerde nur konsequent einen
-- Timeout/noSuchObject bekommen). Der Agent ist bewusst read-only
-- (SNMP v1/v2c, Port 161) - auch OIDs, die intern per "ReadWrite-String-
-- Handler" abgebildet sind, lehnen SNMP SET ab (isSettable=false in der
-- Firmware), siehe Einzelbeschreibungen unten.
--
-- Werte werden geraeteseitig alle 5 Sekunden aktualisiert (kein Live-Read
-- bei jedem GET, "polling optimized") - schnelleres Pollen als 5s liefert
-- wiederholt denselben Cache-Wert.
--
-- Default SNMP-Community: "public" (auf der Einstellungsseite des Geraets
-- aenderbar, Feld "SNMP-Community").
-- ===========================================================================

SENSORMETER-WLAN-MIB DEFINITIONS ::= BEGIN

IMPORTS
    MODULE-IDENTITY, OBJECT-IDENTITY, OBJECT-TYPE, enterprises,
    Integer32, Gauge32, TimeTicks
        FROM SNMPv2-SMI
    DisplayString
        FROM SNMPv2-TC;

smWlanMIB MODULE-IDENTITY
    LAST-UPDATED "202607180000Z"
    ORGANIZATION "Privates Hobby-Projekt (keine Organisation/Firma)"
    CONTACT-INFO
        "Privates Hobby-Projekt ohne offiziellen Support-Kanal.
         Projekt-Repository:
         https://github.com/peterhagelhof7-cmd/sensormeter-wlan"
    DESCRIPTION
        "MIB fuer das Sensormeter-WLAN-Projekt (generisches
         ESP32-WROOM-32-DevKit, WLAN-only, 1x DHT22). Bildet den
         read-only SNMP v1/v2c Agenten unter der privaten Enterprise-OID
         .1.3.6.1.4.1.99999 ab.

         WICHTIG: Enterprise-Nummer 99999 ist eine inoffizielle, NICHT bei
         der IANA registrierte Platzhalter-OID fuer dieses Hobby-Projekt -
         nicht fuer oeffentliche/kommerzielle Nutzung ohne eigene,
         registrierte Enterprise-Number (siehe
         https://www.iana.org/assignments/enterprise-numbers). Nur fuer
         den privaten Einsatz in einem geschlossenen Netz gedacht.

         Enger geschnittenes OID-Schema als Sensormeter/Sensormeter PoE:
         kein LAN-Zweig (.2.1.0), kein Sensor-2-Zweig (.4.x) - dieses
         Geraet hat weder Ethernet noch einen zweiten Sensoreingang.

         Ground truth: firmware/src/SNMPManager.cpp dieses Repositories."
    REVISION    "202607180000Z"
    DESCRIPTION
        "Erste Veroeffentlichung dieser MIB-Datei (10 Objekte)."
    ::= { enterprises 99999 }

-- ---------------------------------------------------------------------------
-- Gruppe 1: System
-- ---------------------------------------------------------------------------

smWlanSystem OBJECT-IDENTITY
    STATUS      current
    DESCRIPTION
        "Systeminformationen: Anzeigename, Firmwareversion, Systemtyp."
    ::= { smWlanMIB 1 }

smWlanSystemName OBJECT-TYPE
    SYNTAX      DisplayString (SIZE (0..32))
    MAX-ACCESS  read-only
    STATUS      current
    DESCRIPTION
        "Anzeigename des Geraets, frei konfigurierbar auf der
         Einstellungsseite ('Systemname'). Intern per SNMP-ReadWrite-
         String-Handler abgebildet, SNMP-SET wird jedoch von der Firmware
         abgelehnt (isSettable=false) - dieser OID ist effektiv
         read-only."
    ::= { smWlanSystem 1 }

smWlanFirmwareVersion OBJECT-TYPE
    SYNTAX      DisplayString
    MAX-ACCESS  read-only
    STATUS      current
    DESCRIPTION
        "Firmware-Versionsstring (z.B. '1.4.2'), statischer Wert aus dem
         Build-Zeit-Makro DEVICE_FIRMWARE_VERSION."
    ::= { smWlanSystem 2 }

smWlanSystemType OBJECT-TYPE
    SYNTAX      DisplayString
    MAX-ACCESS  read-only
    STATUS      current
    DESCRIPTION
        "Fester Systemtyp-String, statisch 'Sensormeter WLAN'. Anders als
         beim Sensormeter- und Sensormeter-PoE-Projekt kein
         konfigurierbares Feld (das WLAN-Projekt hat kein systemType in
         ConfigManager) - hier per addReadOnlyStaticStringHandler
         abgebildet."
    ::= { smWlanSystem 3 }

-- ---------------------------------------------------------------------------
-- Gruppe 2: Netzwerk
--
-- .2.1.0 (LAN-IP) existiert bei diesem Projekt bewusst NICHT - kein
-- Ethernet-Interface. WLAN-IP/RSSI liegen bewusst auf .2.2/.2.3 statt
-- .2.1/.2.2, damit die Basis-OID-Struktur exakt zu Sensormeter/
-- Sensormeter PoE passt (dort .2.1=LAN-IP, .2.2=WLAN-IP, .2.3=WLAN-RSSI).
-- ---------------------------------------------------------------------------

smWlanNetwork OBJECT-IDENTITY
    STATUS      current
    DESCRIPTION
        "Netzwerkstatus: WLAN-IP, WLAN-Signalstaerke. Kein LAN-Zweig
         (.1 unbenutzt/nicht deklariert) - dieses Geraet hat kein
         Ethernet-Interface."
    ::= { smWlanMIB 2 }

smWlanIpAddress OBJECT-TYPE
    SYNTAX      DisplayString (SIZE (7..15))
    MAX-ACCESS  read-only
    STATUS      current
    DESCRIPTION
        "WLAN-IPv4-Adresse als druckbare Punkt-Dezimal-Zeichenkette (z.B.
         '192.168.1.42') - NICHT als binaeres IpAddress-Encoding
         (SNMP-Typ IpAddress); die Firmware liefert hier einen reinen
         ASCII-String. '0.0.0.0' wenn kein WLAN-Link besteht."
    ::= { smWlanNetwork 2 }

smWlanRssi OBJECT-TYPE
    SYNTAX      Integer32
    UNITS       "dBm"
    MAX-ACCESS  read-only
    STATUS      current
    DESCRIPTION
        "WLAN-Empfangsfeldstaerke (RSSI) in dBm, typischerweise negativ
         (z.B. -55). Liefert 0, wenn kein WLAN-Link besteht - 0 dBm ist
         physikalisch kein plausibler RSSI-Messwert und dient hier als
         'kein WLAN' Sentinel-Wert."
    ::= { smWlanNetwork 3 }

-- ---------------------------------------------------------------------------
-- Gruppe 3: Sensor (einziger Sensor dieses Projekts)
--
-- Kein Sensor-2-Zweig (.4.x) - dieses Projekt hat nur einen Sensoreingang,
-- der Zweig ist daher bewusst NICHT als OBJECT-IDENTITY/OBJECT-TYPE in
-- dieser MIB deklariert.
-- ---------------------------------------------------------------------------

smWlanSensor1 OBJECT-IDENTITY
    STATUS      current
    DESCRIPTION
        "Messwerte des einzigen Sensors dieses Geraets (DHT22)."
    ::= { smWlanMIB 3 }

smWlanSensor1Name OBJECT-TYPE
    SYNTAX      DisplayString
    MAX-ACCESS  read-only
    STATUS      current
    DESCRIPTION
        "Fester Anzeigename fuer den Sensor, statisch 'DHT22'."
    ::= { smWlanSensor1 1 }

smWlanSensor1Temperature OBJECT-TYPE
    SYNTAX      Integer32
    UNITS       "0.1 Grad Celsius"
    MAX-ACCESS  read-only
    STATUS      current
    DESCRIPTION
        "Temperatur in Grad Celsius, als Ganzzahl mit Faktor 10
         uebertragen (z.B. 235 = 23.5 Grad C). Liefert 0, wenn keine
         gueltige Sensorlesung vorliegt - ueber SNMP nicht von einer
         echten 0.0-Grad-Messung unterscheidbar."
    ::= { smWlanSensor1 2 }

smWlanSensor1Humidity OBJECT-TYPE
    SYNTAX      Integer32
    UNITS       "0.1 Prozent"
    MAX-ACCESS  read-only
    STATUS      current
    DESCRIPTION
        "Relative Luftfeuchtigkeit in Prozent, als Ganzzahl mit Faktor 10
         uebertragen (z.B. 455 = 45.5 %). 0 bei ungueltiger Lesung,
         siehe smWlanSensor1Temperature."
    ::= { smWlanSensor1 3 }

-- ---------------------------------------------------------------------------
-- Gruppe 5: Status (Gruppe 4 = Sensor 2 existiert bei diesem Projekt nicht,
-- die Nummerierung bleibt trotzdem konsistent zu Sensormeter/Sensormeter
-- PoE, siehe Kopf-Kommentar dieser Datei)
-- ---------------------------------------------------------------------------

smWlanStatus OBJECT-IDENTITY
    STATUS      current
    DESCRIPTION
        "Geraetestatus: Laufzeit, freier Heap-Speicher."
    ::= { smWlanMIB 5 }

smWlanUptime OBJECT-TYPE
    SYNTAX      TimeTicks
    MAX-ACCESS  read-only
    STATUS      current
    DESCRIPTION
        "Geraete-Laufzeit seit dem letzten Boot in Hundertstelsekunden
         (Standard-TimeTicks-Einheit), abgeleitet aus
         esp_timer_get_time(). KEIN sysUpTime-Objekt aus der
         Standard-SNMPv2-MIB (.1.3.6.1.2.1.1.3) - dieser Agent
         implementiert nur den privaten Zweig, nicht MIB-II."
    ::= { smWlanStatus 1 }

smWlanFreeHeap OBJECT-TYPE
    SYNTAX      Gauge32
    UNITS       "Bytes"
    MAX-ACCESS  read-only
    STATUS      current
    DESCRIPTION
        "Freier Heap-Speicher in Bytes (ESP.getFreeHeap())."
    ::= { smWlanStatus 2 }

END
